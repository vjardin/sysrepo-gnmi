module sysrepo-gnmi-monitoring {
  yang-version 1.1;
  namespace "urn:sysrepo:gnmi:monitoring";
  prefix sgm;

  import ietf-yang-types {
    prefix yang;
  }

  description
    "Operational state for the sysrepo-gnmi server.
     Exposes active sessions, subscribe streams, and RPC counters.";

  revision 2026-04-09 {
    description
      "Add get-schema RPC for YANG module download (RFC 6022 equivalent).";
  }

  container server-state {
    config false;

    leaf uptime {
      type uint64;
      units "seconds";
      description
        "Seconds since the server started.";
    }

    leaf active-sessions {
      type uint32;
      description
        "Number of currently tracked client sessions.";
    }

    leaf active-streams {
      type uint32;
      description
        "Total number of active subscribe streams across all sessions.";
    }

    container counters {
      leaf total-rpcs {
        type yang:counter64;
        description
          "Total RPCs received across all sessions.";
      }
      leaf failed-rpcs {
        type yang:counter64;
        description
          "Total RPCs that returned a non-OK status.";
      }
    }

    list session {
      key "id";
      description
        "Active gNMI client sessions.";

      leaf id {
        type uint64;
        description
          "Unique session identifier.";
      }
      leaf peer-address {
        type string;
        description
          "gRPC peer address (IP:port).";
      }
      leaf username {
        type string;
        description
          "NACM username (from metadata or TLS certificate).";
      }
      leaf active-streams {
        type uint32;
        description
          "Number of active subscribe streams for this session.";
      }
      leaf rpc-count {
        type yang:counter64;
        description
          "Total RPCs received on this session.";
      }
      leaf rpc-errors {
        type yang:counter64;
        description
          "RPCs that returned non-OK status on this session.";
      }
    }
  }

  notification gnmi-session-start {
    description
      "A new gNMI client session has been established.";
    leaf session-id {
      type uint64;
    }
    leaf peer-address {
      type string;
    }
    leaf username {
      type string;
    }
  }

  notification gnmi-session-end {
    description
      "A gNMI client session has ended.";
    leaf session-id {
      type uint64;
    }
    leaf peer-address {
      type string;
    }
    leaf reason {
      type enumeration {
        enum closed {
          description "Client disconnected normally.";
        }
        enum idle-timeout {
          description "Session reaped after idle timeout.";
        }
        enum killed {
          description "Session terminated by operator via kill-session.";
        }
        enum resource-exhausted {
          description "Session rejected due to resource limits.";
        }
      }
    }
    leaf killed-by-session-id {
      type uint64;
      description
        "Session ID of the operator that issued kill-session.
         Only present when reason is 'killed'.";
    }
  }

  rpc kill-session {
    description
      "Terminate a gNMI client session by ID. The server releases
       any candidate lock held by the target session and emits a
       gnmi-session-end notification with reason 'killed'.";
    input {
      leaf session-id {
        type uint64;
        mandatory true;
        description
          "ID of the session to terminate.";
      }
    }
    output {
      leaf result {
        type string;
        description
          "Human-readable result message.";
      }
    }
  }

  rpc get-schema {
    description
      "Retrieve the YANG source of an installed module by name and
       optional revision. Equivalent to RFC 6022 get-schema for
       gNMI clients that lack out-of-band schema access.";
    input {
      leaf identifier {
        type string;
        mandatory true;
        description
          "YANG module name (e.g. 'ietf-interfaces').";
      }
      leaf version {
        type string;
        description
          "Module revision date (e.g. '2018-02-20').
           If omitted, the latest implemented revision is returned.";
      }
    }
    output {
      leaf schema {
        type string;
        description
          "YANG module source text.";
      }
    }
  }

  notification gnmi-confirmed-commit {
    description
      "A confirmed-commit lifecycle event.";
    leaf commit-id {
      type string;
    }
    leaf event {
      type enumeration {
        enum start {
          description "Confirmed commit initiated, rollback timer armed.";
        }
        enum confirm {
          description "Commit confirmed and persisted.";
        }
        enum cancel {
          description "Commit cancelled by client.";
        }
        enum timeout-rollback {
          description "Rollback timer expired, config restored.";
        }
      }
    }
  }
}
